/*
 * Copyright (c) 2016 Inocybe Technologies and others.  All rights reserved.
 *
 * This program and the accompanying materials are made available under the
 * terms of the Eclipse Public License v1.0 which accompanies this distribution,
 * and is available at http://www.eclipse.org/legal/epl-v10.html
 */
module spheros {
    yang-version 1;
    namespace "urn:inocybe:opendaylight:summit:spheros";
    prefix "spheros";

    revision "2016-09-26" {
        description "Initial revision of spheros model";
    }

    container roll {
        leaf heading {
            type uint16 {
                range "0 .. 360";
            }
        }
        leaf speed {
            type decimal64 {
                fraction-digits 1;
                range "0.0 .. 1.0";
            }
        }
    }

    container color {
        leaf r {
            type uint8;
        }
        leaf g {
            type uint8;
        }
        leaf b {
            type uint8;
        }
    }
}
